module usecpluginsdni {
    yang-version 1;
    namespace "urn:opendaylight:params:xml:ns:yang:usecpluginsdni";
    prefix "usecpluginsdni";

    revision "2015-01-05" {
        description "Initial revision of usecpluginsdni model";
    }
notification invalidloginattempt{
    description
       "Indicates that the peer connection attempt is invalid.";   
}

rpc peerattemptOnDateTime {
        input {
            leaf dateTime {
                type string;
            }
        }
        output {
           leaf loginAttempt{
                type string;
            }
        }
    }


container peersecurity{
        list loginattempts{
            key time;
            leaf time {
                type string;
            }            
            config false;
        }
    }  
}
