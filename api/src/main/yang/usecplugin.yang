module usecplugin {
    yang-version 1;
    namespace "urn:opendaylight:params:xml:ns:yang:usecplugin";
    prefix "usecplugin";

    revision "2015-01-05" {
        description "Initial revision of usecplugin model";
    }
 
     rpc attackID {
        input {
            leaf NodeID {
                type string;
            }
        }
        output {
            leaf NoOfAttacks{
                type uint16;
            }
        }
    }
    rpc attacksFromIP {
        input {
            leaf SrcIP {
                type string;
            }
        }
        output {
           leaf NoOfAttacks{
                type uint16;
            }
        }
    } 
    rpc attacksToIP {
        input {
            leaf DstIP {
                type string;
            }
        }
        output {
            leaf NoOfAttacks{
                type uint16;
            }
        }
    } 
    rpc attacksInTime {
        input {
            leaf UpwardTime {
                type string;
            }
            leaf Window {
               type uint16;
            }
        }
        output {
            leaf NoOfAttacks{
                type uint16;
            }
        }
    } 
    notification lowWaterMarkBreached{
    description
       "Indicates that the Low Water Mark has Breached.";   
    }
    container LWM {
        list lowwatermark{
            key secKey;
            leaf secKey {
                type string;
            }
            leaf nodeID {
                type string;
            }
            leaf nodeConnectorID {
                type string;
            }
            leaf srcIP {
                type string;
            }
            leaf dstIP {
                type string;
            }
            leaf protocol {
                type string;
            }
            leaf srcPort {
                type uint16;
            }
            leaf dstPort {
                type uint16;
            }
            leaf packetSize {
                type uint16;
            }
            leaf upwardTime {
                type string;
            }
            leaf downwardTime {
                type string;
            }
            config false;
        }
    }
    
       container sample-data-hwm { 
        leaf samples {
            type uint16;
            mandatory true;
        }
        leaf highWaterMark {
            type uint16;
            mandatory true;
        }  
  }  
  
   container sample-data-lwm {
        leaf samples-lwm {
            type uint16;
            mandatory true;
        }
        leaf lowWaterMark-lwm {
            type uint16;
            mandatory true;
        }   
  }  
  
        container HWM {
        list highwatermark {
            key secKey;
            leaf secKey {
                type string;
            }
           leaf nodeID {
                type string;
            }
            leaf nodeConnectorID {
                type string;
            }
            leaf srcIP {
                type string;
            }
            leaf dstIP {
                type string;
            }
            leaf protocol {
                type string;
            }
            leaf srcPort {
                type uint16;
            }
            leaf dstPort {
                type uint16;
            }
            leaf packetSize {
                type uint16;
            }
            leaf upwardTime {
                type string;
            }
            leaf downwardTime {
                type string;
            }

            config false;
        }
    }
    
}
