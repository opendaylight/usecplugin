module usecplugin-impl {
    yang-version 1;
    namespace "urn:opendaylight:params:xml:ns:yang:usecplugin:impl";
    prefix "usecplugin-impl";

    import config { prefix config; revision-date 2013-04-05; }
    import opendaylight-md-sal-binding { prefix md-sal-binding; revision-date 2013-10-28;}

    description
        "Service definition for usecplugin project";

    revision "2014-12-10" {
        description
            "Initial revision";
    }

    identity usecplugin {
        base config:module-type;
        config:java-name-prefix Usecplugin;
    }

    augment "/config:modules/config:module/config:configuration" {
        case usecplugin {
            when "/config:modules/config:module/config:type = 'usecplugin'";
            container broker {
                uses config:service-ref {
                    refine type {
                        mandatory true;
                        config:required-identity md-sal-binding:binding-broker-osgi-registry;
                    }
                }
            }
        }
    }
}
